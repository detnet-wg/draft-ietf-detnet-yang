module ietf-detnet-config {
  namespace "urn:ietf:params:xml:ns:yang:ietf-detnet-config";
  prefix ietf-detnet;

  import ietf-yang-types {
    prefix yang;
  }
  import ietf-inet-types {
    prefix inet;
  }
  import ietf-ethertypes {
    prefix eth;
  }
  import ietf-routing-types {
    prefix rt-types;
  }
  import ietf-packet-fields {
    prefix packet-fields;
  }
  import ietf-interfaces {
    prefix if;
  }

  organization
    "IETF DetNet Working Group";
  contact
    "WG Web:   <http://tools.ietf.org/wg/detnet/>
     WG List:  <mailto: detnet@ietf.org>
     WG Chair: Lou Berger
                 <mailto:lberger@labn.net>

                 Janos Farkas
                 <mailto:janos.farkas@ericsson.com>

     Editor:   Xuesong Geng
                <mailto:gengxuesong@huawei.com>

     Editor:   Mach Chen
                <mailto:mach.chen@huawei.com>

     Editor:   Yeoncheol Ryoo
                <mailto:dbduscjf@etri.re.kr>

     Editor:   Don Fedyk
                <mailto:dfedyk@labn.net>;

     Editor:   Reshad Rahman
                <mailto:rrahman@cisco.com>

     Editor:   Zhenqiang Li
                <mailto:lizhenqiang@chinamobile.com>";
  description
    "This YANG module describes the parameters needed
     for DetNet flow configuration and flow status
     reporting";

  revision 2020-11-12 {
    description
      "initial revision";
    reference
      "RFC XXXX: draft-ietf-detnet-yang-08";
  }

  identity status {
    description
      "Base identity from which all application-status
       actions are derived";
  }

  identity none {
    base status;
    description
      "Application no ingress/egress";
    reference
      "draft-ietf-detnet-flow-information-model Section 5.8";
  }

  identity ready {
    base status;
    description
      "Application ingress/egress ready";
    reference
      "draft-ietf-detnet-flow-information-model Section 5.8";
  }

  identity failed {
    base status;
    description
      "Application ingres/egresss failed";
    reference
      "draft-ietf-detnet-flow-information-model Section 5.8";
  }

  identity out-of-service {
    base status;
    description
      "Application Administratively blocked";
    reference
      "draft-ietf-detnet-flow-information-model Section 5.8";
  }

  identity partial-failed {
    base status;
    description
      "Application One or more Egress ready, and one or more Egress
       failed.  The DetNet flow can be used if the Ingress is
       Ready.";
    reference
      "draft-ietf-detnet-flow-information-model Section 5.8";
  }

  typedef app-flow-ref {
    type leafref {
      path "/ietf-detnet:detnet"
         + "/ietf-detnet:app-flows"
         + "/ietf-detnet:app-flow"
         + "/ietf-detnet:name";
    }
  }

  typedef service-sub-layer-ref {
    type leafref {
      path "/ietf-detnet:detnet"
         + "/ietf-detnet:service-sub-layer"
         + "/ietf-detnet:service-sub-layer-list"
         + "/ietf-detnet:name";
    }
  }

  typedef forwarding-sub-layer-ref {
    type leafref {
      path "/ietf-detnet:detnet"
         + "/ietf-detnet:forwarding-sub-layer"
         + "/ietf-detnet:forwarding-sub-layer-list"
         + "/ietf-detnet:name";
    }
  }

  typedef traffic-profile-ref {
    type leafref {
      path "/ietf-detnet:detnet"
         + "/ietf-detnet:traffic-profile"
         + "/ietf-detnet:profile-number";
    }
  }

  typedef ipsec-spi {
    type uint32 {
      range "1..max";
    }
    description
      "SPI";
  }

  typedef service-operation-type {
    type enumeration {
      enum service-initiation {
        description
          "Operation for DetNet service sub-layer encapsulation";
      }
      enum service-termination {
        description
          "Operation for DetNet service sub-layer decapsulation";
      }
      enum service-relay {
        description
          "Operation for DetNet service sub-layer swap";
      }
      enum non-detnet {
        description
          "No operation for DetNet service sub-layer";
      }
    }
  }

  typedef forwarding-operations-type {
    type enumeration {
      enum forward {
        description
          "Operation forward to next-hop";
      }
      enum impose-and-forward {
        description
          "Operation impose outgoing label(s) and forward to
           next-hop";
      }
      enum pop-and-forward {
        description
          "Operation pop incoming label and forward to next-hop";
      }
      enum pop-impose-and-forward {
        description
          "Operation pop incoming label, impose one or more
           outgoing label(s) and forward to next-hop";
      }
      enum swap-and-forward {
        description
          "Operation swap incoming label, with outgoing label and
           forward to next-hop";
      }
      enum pop-and-lookup {
        description
          "Operation pop incoming label and perform a lookup";
      }
    }
    description
      "MPLS operations types";
  }

  typedef service-protection-type {
    type enumeration {
      enum none {
        description
          "no service protection provide";
      }
      enum replication {
        description
          "A Packet Replication Function (PRF) replicates
           DetNet flow packets and forwards them to one or
           more next hops in the DetNet domain.  The number
           of packet copies sent to each next hop is a
           DetNet flow specific parameter at the node doing
           the replication.  PRF can be implemented by an
           edge node, a relay node, or an end system";
      }
      enum elimination {
        description
          "A Packet Elimination Function (PEF) eliminates
           duplicate copies of packets to prevent excess
           packets flooding the network or duplicate
           packets being sent out of the DetNet domain.
           PEF can be implemented by an edge node, a relay
           node, or an end system.";
      }
      enum ordering {
        description
          "A Packet Ordering Function (POF) re-orders
           packets within a DetNet flow that are received
           out of order.  This function can be implemented
           by an edge node, a relay node, or an end system.";
      }
      enum elimination-ordering {
        description
          "A combination of PEF and POF that can be
           implemented by an edge node, a relay node, or
           an end system.";
      }
      enum elimination-replication {
        description
          "A combination of PEF and PRF that can be
           implemented by an edge node, a relay node, or
           an end system";
      }
      enum elimination-ordering-replicaiton {
        description
          "A combination of PEF, POF and PRF that can be
           implemented by an edge node, a relay node, or
           an end system";
      }
    }
  }

  typedef sequence-number-generation-type {
    type enumeration {
      enum copy-from-app-flow {
        description
          "Copy the app-flow sequence number to the DetNet-flow";
      }
      enum generate-by-detnet-flow {
        description
          "Generate the sequence number by DetNet flow";
      }
    }
  }

  typedef sequence-number-field {
    type enumeration {
      enum zero-sn {
        description
          "there is no DetNet sequence number field.";
      }
      enum short-sn {
        value 16;
        description
          "there is 16bit DetNet sequence number field";
      }
      enum long-sn {
        value 28;
        description
          "there is 28bit DetNet sequence number field";
      }
    }
  }

  grouping ip-header {
    description
      "The IPv4/IPv6 packet header information";
    leaf src-ip-address {
      type inet:ip-address;
      description
        "The source IP address of the header";
    }
    leaf dest-ip-address {
      type inet:ip-address;
      description
        "The destination IP address of the header";
    }
    leaf next-header {
      type uint8;
      description
        "The next header of the IPv6 header";
    }
    leaf traffic-class {
      type uint8;
      description
        "The traffic class value of the header";
    }
    leaf flow-label {
      type inet:ipv6-flow-label;
      description
        "The flow label value of the header";
    }
    leaf source-port {
      type inet:port-number;
      description
        "The source port number";
    }
    leaf destination-port {
      type inet:port-number;
      description
        "The destination port number";
    }
  }

  grouping l2-header {
    description
      "The Ethernet or TSN packet header information";
    leaf source-mac-address {
      type yang:mac-address;
      description
        "The source MAC address value of the Ethernet header";
    }
    leaf destination-mac-address {
      type yang:mac-address;
      description
        "The destination MAC address value of the Ethernet header";
    }
    leaf ethertype {
      type eth:ethertype;
      description
        "The Ethernet packet type value of the Ethernet header";
    }
    leaf vlan-id {
      type uint16;
      description
        "The VLAN value of the Ethernet header";
    }
    leaf pcp {
      type uint8;
      description
        "The priority value of the Ethernet header";
    }
  }

  grouping destination-ip-port-identification {
    description
      "The TCP/UDP port(source/destination) identification information";
    container destination-port {
      uses packet-fields:port-range-or-operator;
    }
  }

  grouping source-ip-port-identification {
    description
      "The TCP/UDP port(source/destination) identification information";
    container source-port {
      uses packet-fields:port-range-or-operator;
    }
  }

  grouping ip-flow-identification {
    description
      "The IPv4/IPv6 packet header identification information";
    leaf src-ip-prefix {
      type inet:ip-prefix;
      description
        "The source IP address of the header";
    }
    leaf dest-ip-prefix {
      type inet:ip-prefix;
      description
        "The destination IP address of the header";
    }
    leaf next-header {
      type uint8;
      description
        "The next header of the IPv6 header";
    }
    leaf traffic-class {
      type uint8;
      description
        "The traffic class value of the header";
    }
    leaf flow-label {
      type inet:ipv6-flow-label;
      description
        "The flow label value of the header";
    }
    uses source-ip-port-identification;
    uses destination-ip-port-identification;
    leaf ipsec-spi {
      type ipsec-spi;
      description
        "Security parameter index of SA entry";
    }
  }

  grouping mpls-flow-identification {
    description
      "The MPLS packet header identification information";
    choice label-space {
      description
        "";
      case context-label-space {
        uses rt-types:mpls-label-stack;
      }
      case platform-label-space {
        leaf label {
          type rt-types:mpls-label;
        }
      }
    }
  }

  grouping traffic-specification {
    container traffic-specification {
      description
        "traffic-specification specifies how the Source
         transmits packets for the flow.  This is the
         promise/request of the Source to the network.
         The network uses this traffic specification
         to allocate resources and adjust queue
         parameters in network nodes.";
      reference
        "draft-ietf-detnet-flow-information-model Section 4.1";
      leaf interval {
        type uint32;
        description
          "The period of time in which the traffic
           specification cannot be exceeded";
      }
      leaf max-packets-per-interval {
        type uint32;
        description
          "The maximum number of packets that the
           source will transmit in one Interval.";
      }
      leaf max-payload-size {
        type uint32;
        description
          "The maximum payload size that the source
           will transmit.";
      }
      leaf average-packets-per-interval {
        type uint32;
        description
          "The average number of packets that the
           source will transmit in one Interval";
      }
      leaf average-payload-size {
        type uint32;
        description
          "The average payload size that the
           source will transmit.";
      }
    }
  }

  grouping traffic-requirements {
    container traffic-requirements {
      description
        "FlowRequirements: defines the attributes of the App-flow
         regarding bandwidth, latency, latency variation, loss, and
         misordering tolerance.";
      reference
        "draft-ietf-detnet-flow-information-model Section 4.2";
      leaf min-bandwidth {
        type uint64;
        description
          "MinBandwidth is the minimum bandwidth that has to be
           guaranteed for the DetNet service.  MinBandwidth is
           specified in octets per second.";
      }
      leaf max-latency {
        type uint32;
        description
          "MaxLatency is the maximum latency from Ingress to Egress(es)
           for a single packet of the DetNet flow.  MaxLatency is
           specified as an integer number of nanoseconds";
      }
      leaf max-latency-variation {
        type uint32;
        description
          "MaxLatencyVariation is the difference between the minimum and
           the maximum end-to-end one-way latency.  MaxLatencyVariation
           is specified as an integer number of nanoseconds.";
      }
      leaf max-loss {
        type uint8;
        description
          "MaxLoss defines the maximum Packet Loss Ratio (PLR) parameter
           for the DetNet service between the Ingress and Egress(es) of
           the DetNet domain.";
      }
      leaf max-consecutive-loss-tolerance {
        type uint32;
        description
          "Some applications have special loss requirement, such as
           MaxConsecutiveLossTolerance.  The maximum consecutive loss
           tolerance parameter describes the maximum number of
           consecutive packets whose loss can be tolerated.  The maximum
           consecutive loss tolerance can be measured for example based
           on sequence number";
      }
      leaf max-misordering {
        type uint32;
        description
          "MaxMisordering describes the tolerable maximum number of
           packets that can be received out of order.  The maximum
           allowed misordering can be measured for example based on
           sequence number.  The value zero for the maximum allowed
           misordering indicates that in order delivery is required,
           misordering cannot be tolerated.";
      }
    }
  }

  grouping data-flow-spec {
    description
      "app-flow identification";
    choice data-flow-type {
      case tsn-app-flow {
        uses l2-header;
      }
      case ip-app-flow {
        uses ip-flow-identification;
      }
      case mpls-app-flow {
        uses mpls-flow-identification;
      }
    }
  }

  grouping detnet-flow-spec {
    description
      "detnet-flow identification";
    choice detnet-flow-type {
      case ip-detnet-flow {
        uses ip-flow-identification;
      }
      case mpls-detnet-flow {
        uses mpls-flow-identification;
      }
    }
  }

  grouping app-flows-ref {
    description
      "incoming or outgoing app-flow reference group";
    leaf-list flow-list{
      type app-flow-ref;
      description
        "List of ingress or egress app-flows";
    }
  }

  grouping service-sub-layer-ref {
    description
      "incoming or outgoing service sub-layer reference group";
    leaf-list service-sub-layer {
      type service-sub-layer-ref;
      description
        "List of incoming or outgoing service sub-layer
         that has to aggregate or disaggregate";
    }
  }

  grouping forwarding-sub-layer-ref {
    description
      "incoming or outgoing forwarding sub-layer reference group";
    leaf-list forwarding-sub-layer {
      type forwarding-sub-layer-ref;
      description
        "List of incoming or outgoing forwarding sub-layer
         that has to aggregate or disaggregate";
    }
  }

  grouping detnet-header {
    description
      "DetNet header info for DetNet encapsulation or swap";
    choice header-type {
      case detnet-mpls-header {
        description
          "MPLS label stack for DetNet MPLS encapsulation or forwarding";
        uses rt-types:mpls-label-stack;
      }
      case detnet-ip-header {
        description
          "IPv4/IPv6 packet header for DetNet IP encapsulation";
        uses ip-header;
      }
    }
  }

  grouping detnet-app-next-hop-content {
    description
      "Generic parameters of DetNet next hops.";
    choice next-hop-options {
      mandatory true;
      description
        "Options for next hops.
         It is expected that further cases will be added through
         augments from other modules, e.g., for recursive
         next hops.";
      case simple-next-hop {
        description
          "This case represents a simple next hop consisting of the
           next-hop address and/or outgoing interface.
           Modules for address families MUST augment this case with a
           leaf containing a next-hop address of that address
           family.";
        leaf outgoing-interface {
          type if:interface-ref;
        }
        choice flow-type {
          case ip {
            leaf next-hop-address {
              type inet:ip-address;
            }
          }
          case mpls {
            uses rt-types:mpls-label-stack;
          }
        }
      }
      case next-hop-list {
        container next-hop-list {
          description
            "Container for multiple next hops.";
          list next-hop {
            key "hop-index";
            description
              "An entry in a next-hop list.
               Modules for address families MUST augment this list
               with a leaf containing a next-hop address of that
               address family.";
            leaf hop-index {
              type uint8;
              description
                "";
            }
            leaf outgoing-interface {
              type if:interface-ref;
            }
            choice flow-type {
              case ip {
                leaf next-hop-address {
                  type inet:ip-address;
                }
              }
              case mpls {
                uses rt-types:mpls-label-stack;
              }
            }
          }
        }
      }
    }
  }

  grouping detnet-forwarding-next-hop-content {
    description
      "Generic parameters of DetNet next hops.";
    choice next-hop-options {
      mandatory true;
      description
        "Options for next hops.
         It is expected that further cases will be added through
         augments from other modules, e.g., for recursive
         next hops.";
      case simple-next-hop {
        description
          "This case represents a simple next hop consisting of the
           next-hop address and/or outgoing interface.
           Modules for address families MUST augment this case with a
           leaf containing a next-hop address of that address
           family.";
        leaf outgoing-interface {
          type if:interface-ref;
        }
        choice flow-type {
          case ip {
            choice operation-type {
              case ip-forwarding {
                leaf next-hop-address {
                  type inet:ip-address;
                }
              }
              case mpls-over-ip-encapsulation {
                uses ip-header;
              }
            }
          }
          case mpls {
            uses rt-types:mpls-label-stack;
          }
        }
      }
      case next-hop-list {
        container next-hop-list {
          description
            "Container for multiple next hops.";
          list next-hop {
            key "hop-index";
            description
              "An entry in a next-hop list.

               Modules for address families MUST augment this list
               with a leaf containing a next-hop address of that
               address family.";
            leaf hop-index {
              type uint8;
              description
                "";
            }
            leaf outgoing-interface {
              type if:interface-ref;
            }
            choice flow-type {
              case ip {
                choice operation-type {
                  case ip-forwarding {
                    leaf next-hop-address {
                      type inet:ip-address;
                    }
                  }
                  case mpls-over-ip-encapsulation {
                    uses ip-header;
                  }
                }
              }
              case mpls {
                uses rt-types:mpls-label-stack;
              }
            }
          }
        }
      }
    }
  }

  container detnet {
    list traffic-profile {
      key "profile-number";
      description
        "A traffic profile";
      leaf profile-number {
        type uint16;
        description
          "An Aggregation group ID. Zero means the service is not
           part of a group";
      }
      uses traffic-requirements;
      uses traffic-specification;
      leaf-list member-applications {
        type app-flow-ref; 
        config false;
        description
          "Applications attached to this profile";
      }
      leaf-list member-services {
        type service-sub-layer-ref;
        config false;
        description
          "Services attached to this profile";
      }
      leaf-list member-forwarding-sublayers {
        type forwarding-sub-layer-ref;
        config false;
        description
          "Forwarding sub-layer attached to this profile";
      }
    }
    container app-flows {
      description
        "The DetNet app-flow configuration";
      reference
        "draft-ietf-detnet-flow-information-model Section Section 4.1";
      list app-flow {
        key "name";
        description
          "A unique (management) identifier of the App-flow.";
        leaf name {
          type string;
          description
            "A unique (management) identifier of the App-flow.";
          reference
            "draft-ietf-detnet-flow-information-model 
             Sections 4.1, 5.1";
        }
        leaf app-flow-bidir-congruent {
          type boolean;
          description
            "Defines the data path requirement of the App-flow whether
             it must share the same data path and physical path
             for both directions through the network,
             e.g., to provide congruent paths in the two directions.";
          reference
            "draft-ietf-detnet-flow-information-model Section 4.2";
        }
        leaf outgoing-service {
          type service-sub-layer-ref;
          config false;
          description
            "Binding to this applications outgoing
             service";
        }
        leaf incoming-service {
          type service-sub-layer-ref;
          config false;
          description
            "Binding to this applications incoming
             service";
        }
        leaf traffic-profile {
          type traffic-profile-ref;
          description
            "The Traffic Profile for this group";
        }
        container ingress {
          // key "name";  This should be a list for aggregation
          description
            "Ingress DetNet application flows or a compound flow";
          leaf name {
            type string;
            description
              "Ingress DetNet application";
          }
          leaf app-flow-status {
            type identityref {
              base status;
            }
            config false;
            description
              "Status of ingress application flow";
            reference
              "draft-ietf-detnet-flow-information-model 
               Sections 4.1, 5.8";
          }
          leaf interface {
            type if:interface-ref;
          }
          uses data-flow-spec;
        } //End of app-ingress
        container egress {
          description
            "Route's next-hop attribute.";
          // key "name";  This should be a list for aggregation
          leaf name {
            type string;
            description
              "Egress DetNet application";
          }
          choice application-type {
            container Ethernet {
              leaf Ethernet-place-holder {
                type string;
                description
                  "Place holder for matching Ethernet";
              }
            }
            container ip-mpls {
              uses detnet-app-next-hop-content;
            }
          }
        }
      }
    }
    container service-sub-layer {
      description
        "The DetNet service sub-layer configuration";
      list service-sub-layer-list {
        key "name";
        description
          "";
        leaf name {
          type string;
          description
            "The name of the DetNet service sub-layer";
        }
        leaf service-rank {
          type uint8;
          description
            "The DetNet rank for this service";
          reference
            "draft-ietf-detnet-flow-information-model Section 5.7";
        }
        leaf traffic-profile {
          type traffic-profile-ref;
          description
            "The Traffic Profile for this service";
        }
        container service-protection {
          leaf service-protection-type {
            type service-protection-type;
            description
              "The DetNet service protection type such as PRF, PEF,
               PEOF,PERF, and PEORF";
          }
          leaf sequence-number-length {
            type sequence-number-field;
            description
              "Sequence number field can choice 0 bit, 16bit, 28 bit
               filed";
          }
        }
        leaf service-operation-type {
          type service-operation-type;
        }
        container incoming-type {
          description
            "The DetNet service sub-layer incoming configuration.";
          choice incoming-type {
            mandatory true;
            description
              "";
            container app-flow {
              description
                "This service sub-layer is related to
                 the app-flows of the upper layer
                 and provide ingress proxy or ingress aggregation
                 at the ingress node.";
              uses app-flows-ref;
            }
            container service {
              description
                "This service sub-layer is related to
                 the service sub-layer of the upper layer
                 and provide service-to-service aggregation
                 at the ingress node or relay node.";
              uses service-sub-layer-ref;
            }
            container forwarding {
              description
                "This service sub-layer is related to
                 the forwarding sub-layer of the upper layer
                 and provide forwarding-to-service aggregation
                 at the ingress node or relay node.";
              uses forwarding-sub-layer-ref;
            }
            container service-identification {
              description
                "This service sub-layer is related to
                 the service or forwarding sub-layer of the lower layer
                 and provide DetNet service relay or termination
                 at the relay node or egress node.";
              uses detnet-flow-spec;
            }
          }
        }
        container outgoing-type {
          description
            "The DetNet service sub-layer outgoing configuration.";
          choice outgoing-type {
            mandatory true;
            description
              "";
            container forwarding-sub-layer {
              description
                "This service sub-layer is sent to the forwarding
                 sub-layers of the lower layer for DetNet service
                 forwarding or service-to-forwarding aggregation at
                 the ingress node or relay node.  When the operation
                 type is service-initiation, The service sub-layer
                 encapsulates the DetNet Control-Word and services
                 label, which are for individual DetNet flow when the
                 incoming type is app-flow and for aggregated DetNet
                 flow when the incoming type is service or
                 forwarding.  The service sub-layer swaps the service
                 label when the operation type is service-relay.";
              uses detnet-flow-spec;
              list service-outgoing-list {
                key "service-outgoing-index";
                description
                  "list of the outgoing service
                   that separately for each node
                   where services will be eliminated";
                leaf service-outgoing-index {
                  type uint8;
                }
                uses detnet-header;
                list forwarding-sub-layer {
                  key "index";
                  description
                    "list of the forwarding-sub-layer
                     for replicate to multiple paths";
                  leaf index {
                    type uint8;
                  }
                  leaf forwarding-sub-layer {
                    type forwarding-sub-layer-ref;
                    description
                      "forwarding-sub-layer reference point";
                  }
                }
              }
            }
            container service-sub-layer {
              description
                "This service sub-layer is sent to the service
                 sub-layers of the lower layer for service-to-service
                 aggregation at the ingress node or relay node.  The
                 service sub-layer encapsulates the DetNet
                 Control-Word and S-label when the operation type is
                 service-initiation, and swaps the S-label when the
                 operation type is service-relay.";
              leaf aggregation-service-sub-layer {
                type service-sub-layer-ref;
                description
                  "reference point of the service-sub-layer
                   at which this service will be aggregated";
              }
              container service-label {
                uses rt-types:mpls-label-stack;
              }
            }
            container upper-app-flow {
              description
                "This service sub-layer is sent to the app-flow of
                 the upper layer for egress proxy at the egress node,
                 and decapsulates the DetNet Control-Word and S-label
                 for individual DetNet service.  This outgoing type
                 only can be chosen when the operation type is
                 service-termination.";
              uses app-flows-ref;
            }
            container upper-service-sub-layer {
              description
                "This service sub-layer is sent to the service
                 sub-layer of the upper layer for service-to-service
                 disaggregation at the relay node or egress node, and
                 decapsulates the DetNet Control-Word and A-label for
                 aggregated DetNet service.  This outgoing type only
                 can be chosen when the operation type is
                 service-termination.";
              uses service-sub-layer-ref;
            }
            container upper-forwarding-sub-layer {
              description
                "This service sub-layer is sent to the forwarding
                 sub-layer of the upper layer for
                 forwarding-to-service disaggregation at the relay
                 node or egress node, and decapsulates the DetNet
                 Control-Word and A-label for aggregated DetNet
                 service.  This outgoing type only can be chosen when
                 the operation type is service-termination";
              uses forwarding-sub-layer-ref;
            }
          }
        }
      }
    }
    container forwarding-sub-layer {
      description
        "The DetNet forwarding sub-layer configuration";
      list forwarding-sub-layer-list {
        key "name";
        description
          "";
        leaf name {
          type string;
          description
            "The name of the DetNet forwarding sub-layer";
        }
        leaf traffic-profile {
          type traffic-profile-ref;
          description
            "The Traffic Profile for this group";
        }
        leaf forwarding-operation-type {
          type forwarding-operations-type;
        }
        container incoming-type {
          description
            "The DetNet forwarding sub-layer incoming configuration.";
          choice incoming-type {
            mandatory true;
            description
              "Cases of incoming types";
            container service-sub-layer {
              description
                "This forwarding sub-layer is related to the service
                 sub-layers of the upper layer and provide DetNet
                 forwarding or service-to-forwarding aggregation at
                 the ingress node or relay node.";
              leaf-list sub-layer-list {
                type service-sub-layer-ref;
                config false;
                description
                  "";
              }
            }
            case upper-forwarding-sub-layer {
              description
                "This forwarding sub-layer is related to the
                 forwarding sub-layer of the upper layer and provide
                 forwarding-to-forwarding aggregation at the ingress
                 node or relay node or transit node.";
              uses forwarding-sub-layer-ref;
            }
            case lower-forwarding-sub-layer {
            //case forwarding-identification {
              description
                "This forwarding sub-layer is related to all of the
                 lower layer and provide DetNet forwarding swap or
                 termination at the transit node or relay node or
                 egress node.";
              leaf interface {
                type if:interface-ref;
                description
                  "This is the interface associated with the forwarding
                   sub-layer";
              }
              uses detnet-flow-spec;
            }
          }
        }
        container outgoing-type {
          description
            "The DetNet forwarding sub-layer outbound configuration.";
          choice outgoing-type {
            mandatory true;
            description
              "";
            container interface {
              description
                "This forwarding sub-layer is sent to the interface
                 for send to next-hop at the ingress node or relay
                 node or transit node.";
              uses detnet-forwarding-next-hop-content;
            }
            case service {
              description
                "This forwarding sub-layer is sent to the service
                 sub-layers of the lower layer for
                 forwarding-to-service aggregation at the ingress
                 node or relay node.";
              leaf aggregation-service-sub-layer {
                type service-sub-layer-ref;
              }
              container optional-forwarding-label {
                uses rt-types:mpls-label-stack;
              }
            }
            case forwarding {
              description
                "This forwarding sub-layer is sent to the forwarding
                 sub-layers of the lower layer for
                 forwarding-to-forwarding aggregation at the ingress
                 node or relay node or transit node.";
              leaf aggregation-forwarding-sub-layer {
                type forwarding-sub-layer-ref;
              }
              container forwarding-label {
                uses rt-types:mpls-label-stack;
              }
            }
            case upper-service {
              description
                "This forwarding sub-layer is sent to the service
                 sub-layer of the upper layer and decapsulate the
                 F-label for DetNet service or service-to-forwarding
                 disaggregation at the relay node or egress node.
                 This outgoing type only can be chosen when the
                 operation type is pop-and-lookup";
              uses service-sub-layer-ref;
            }
            case upper-forwarding {
              description
                "This forwarding sub-layer is sent to the forwarding
                 sub-layer of the upper layer and decapsulate the
                 F-label for forwarding-to-forwarding disaggregation
                 at the transit node or relay node or egress node.
                 This outgoing type only can be chosen when the
                 operation type is pop-and-lookup";
              uses forwarding-sub-layer-ref;
            }
          }
        }
      }
    }
  }
}
