module ietf-detnet {
  yang-version 1.1;
  namespace "urn:ietf:params:xml:ns:yang:ietf-detnet";
  prefix dnet;

  import ietf-yang-types {
    prefix yang;
    reference
      "RFC 6991 - Common YANG Data Types.";
  }
  import ietf-inet-types {
    prefix inet;
    reference
      "RFC 6991 - Common YANG Data Types.";
  }
  import ietf-ethertypes {
    prefix ethertypes;
    reference
      "RFC 8519 - YANG Data Model for Network Access Control
                  Lists (ACLs).";
  }
  import ietf-routing-types {
    prefix rt-types;
    reference
      "RFC 8294 - Common YANG Data Types for the Routing Area.";
  }
  import ietf-packet-fields {
    prefix packet-fields;
    reference
      "RFC 8519 - YANG Data Model for Network Access Control Lists
       (ACLs).";
  }
  import ietf-interfaces {
    prefix if;
    reference
      "RFC 8343 - A YANG Data Model for Interface Management.";
  }
  import ieee802-dot1q-types {
    prefix dot1q-types;
    reference
      "IEEE 802.1Q-2022 - IEEE Standard for Local and Metropolitan
       Area Networks--Bridges and Bridged Networks Clause 48: YANG
       Data Models.";
  }

  organization
    "IETF DetNet Working Group";

  contact
    "WG Web:   <https://datatracker.ietf.org/wg/detnet/>
     WG List:  <mailto:detnet@ietf.org>

     Editor:   Xuesong Geng
                <mailto:gengxuesong@huawei.com>

     Editor:   Yeoncheol Ryoo
                <mailto:dbduscjf@etri.re.kr>

     Editor:   Don Fedyk
                <mailto:dfedyk@labn.net>;

     Editor:   Reshad Rahman
                <mailto:reshad@yahoo.com>

     Editor:   Zhenqiang Li
                <mailto:lizhenqiang@chinamobile.com>";
  description
    "This YANG module describes the parameters needed
     for DetNet flow configuration and flow status
     reporting. This YANG module conforms to the Network 
     Management Datastore Architecture (NMDA).
     
     Copyright (c) 2024 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX;
     see the RFC itself for full legal notices.";

     // RFC Ed.: replace XXXX with actual RFC number and remove
     // this note

     // replace '2024-02-21' with the module publication date
     // the format is (year-month-day)    

  revision 2024-02-21 {
    description
      "Initial revision";
    reference
      "RFC XXXX: Deterministic Networking (DetNet) YANG Model";
  }

  identity app-status {
    description
      "Base identity from which all application-status
       status types are derived.";
    reference
      "RFC 9016 Section 5.8";
  }

  identity none {
    base app-status;
    description
      "This application has no status. This identity is
       expected when the configuration is incomplete.";
    reference
      "RFC 9016 Section 5.8";
  }

  identity ready {
    base app-status;
    description
      "Application ingress/egress ready.";
    reference
      "RFC 9016 Section 5.8";
  }

  identity failed {
    base app-status;
    description
      "Application ingres/egress failed.";
    reference
      "RFC 9016 Section 5.8";
  }

  identity out-of-service {
    base app-status;
    description
      "Application administratively blocked.";
    reference
      "RFC 9016 Section 5.8";
  }

  identity partial-failed {
    base app-status;
    description
      "This is an application with one or more Egress ready, and one
       or more Egress failed.  The DetNet flow can be used if the
       Ingress is Ready.";
    reference
      "RFC 9016 Section 5.8";
  }

  typedef app-flow-ref {
    type leafref {
      path "/dnet:detnet"
         + "/dnet:app-flows"
         + "/dnet:app-flow"
         + "/dnet:name";
    }
    description
      "This is an application Reference.";
  }

  typedef service-sub-layer-ref {
    type leafref {
      path "/dnet:detnet"
         + "/dnet:service"
         + "/dnet:sub-layer"
         + "/dnet:name";
    }
    description
      "This is a service sub-layer Reference.";
  }

  typedef forwarding-sub-layer-ref {
    type leafref {
      path "/dnet:detnet"
         + "/dnet:forwarding"
         + "/dnet:sub-layer"
         + "/dnet:name";
    }
    description
      "This is a forwarding sub-layer Reference.";
  }

  typedef traffic-profile-ref {
    type leafref {
      path "/dnet:detnet"
         + "/dnet:traffic-profile"
         + "/dnet:name";
    }
    description
      "This is a traffic Profile Reference.";
  }

  typedef ipsec-spi {
    type uint32 {
      range "1..max";
    }
    description
      "IPsec Security Parameters Index. A 32 bit value
       where some values are reserved.";
    reference
      "IETF RFC 4303 Encapsulating Security Payload (ESP).";
  }

  typedef operation {
    type enumeration {
      enum initiation {
        description
          "This is an initiating service sub-layer encapsulation.";
      }
      enum termination {
        description
          "Operation for DetNet service sub-layer decapsulation.";
      }
      enum relay {
        description
          "Operation for DetNet service sub-layer swap.";
      }
      enum non-detnet {
        description
          "No operation for DetNet service sub-layer.";
      }
    }
    description
      "Operation type identifies the behavior for this service
       sub-layer. Operations are described as unidirectional
       but a service sub-layer may combine operation types.";
  }

  typedef mpls-fwd-operation {
    type enumeration {
      enum impose-and-forward {
        description
          "This operation imposes outgoing label(s) and forwards to
           next-hop.";
        reference
          " A YANG Data Model for MPLS Base RFC 8960.";
      }
      enum pop-and-forward {
        description
          "This operation pops the incoming label and forwards to
           the next-hop.";
        reference
          " A YANG Data Model for MPLS Base RFC 8960.";
      }
      enum pop-impose-and-forward {
        description
          "This operation pops the incoming label, imposes one or
           more outgoing label(s) and forwards to the next-hop.";
        reference
          " A YANG Data Model for MPLS Base RFC 8960.";
      }
      enum swap-and-forward {
        description
          "This operation swaps an incoming label, with an outgoing
           label and forwards to the next-hop.";
        reference
          " A YANG Data Model for MPLS Base RFC 8960.";
      }
      enum forward {
        description
          "This operation forwards to next-hop.";
      }
      enum pop-and-lookup {
        description
          "This operation pops an incoming label and performs a
           lookup.";
      }
    }
    description
      "MPLS operations types.  This is an enum modeled after the
       MPLS enum.  The enums are the same as A YANG Data Model 
       for MPLS Base. RFC 8960.";
  }

  typedef service-protection {
    type enumeration {
      enum none {
        description
          "No service protection provided.";
      }
      enum replication {
        description
          "A Packet Replication Function (PRF) replicates DetNet
           flow packets and forwards them to one or more next hops in
           the DetNet domain.  The number of packet copies sent to
           each next hop is a DetNet flow-specific parameter at the
           node doing the replication.  PRF can be implemented by an
           edge node, a relay node, or an end system.";
      }
      enum elimination {
        description
          "A Packet Elimination Function (PEF) eliminates duplicate
           copies of packets to prevent excess packets flooding the
           network or duplicate packets being sent out of the DetNet
           domain.  PEF can be implemented by an edge node, a relay
           node, or an end system.";
      }
      enum ordering {
        description
          "A Packet Ordering Function (POF) re-orders packets within
           a DetNet flow that are received out of order.  This
           function can be implemented by an edge node, a relay node,
           or an end system.";
      }
      enum elimination-ordering {
        description
          "A combination of PEF and POF that can be implemented by
           an edge node, a relay node, or an end system.";
      }
      enum elimination-replication {
        description
          "A combination of PEF and PRF that can be implemented by
           an edge node, a relay node, or an end system.";
      }
      enum elimination-ordering-replication {
        description
          "A combination of PEF, POF and PRF that can be implemented
           by an edge node, a relay node, or an end system.";
      }
    }
    description
      "This typedef describes the service protection enumeration
       values.";
  }

  typedef sequence-number-generation {
    type enumeration {
      enum copy-from-app-flow {
        description
          "Copy-from-app-flow is used to extend and use the
          sequence number used in App-flow. This function is
          required when encapsulating App-flows that have been
          replicated and received through multiple ingress nodes
          into a member flow, and then eliminate it at the relay
          node.";
     }
      enum generate-by-detnet-flow {
        description
          "Generate-by-detnet-flow is used to create a new
          sequence number for a DetNet flow at the ingress node.
          Care must be taken when using this option to ensure
          there is only one source for generating sequence
          numbers.";
      }
    }
    description
      "This typedef defines how to generate sequence numbers to
      be used in DetNet encapsulation."; 
  }
  typedef sequence-number-field {
    type enumeration {
      enum zero-sn {
        description
          "No DetNet sequence number field is used.";
      }
      enum short-sn {
        value 16;
        description
          "A 16-bit DetNet sequence number field is used.";
      }
      enum long-sn {
        value 28;
        description
          "A 28-bit DetNet sequence number field is used.";
      }
    }
    description
      "This enumeration configures the sequence number behavior.";
  }

  grouping ip-header {
    description
      "This grouping captures the IPv4/IPv6 packet header
       information. It is modeled after existing fields.";
    leaf src-ip-address {
      type inet:ip-address-no-zone;
      description
        "The source IP address in the header.";
      reference
        "RFC 6991 Common YANG Data Types";
    }
    leaf dest-ip-address {
      type inet:ip-address-no-zone;
      description
        "The destination IP address in the header.";
      reference
        "RFC 6991 Common YANG Data Types";
    }
    leaf protocol-next-header {
      type uint8;
      description
        "In IPv4 refers to the protocol of the
         payload.  In IPv6, this field is known as 'next-header',
         and Identifies the type of header immediately following
         the IPv6 header.";
      reference
        "RFC 791: Internet Protocol
         RFC 8200: Internet Protocol, Version 6 (IPv6)
         Specification.";
    }
    leaf dscp {
      type inet:dscp;
      description
        "The traffic class value in the header.";
      reference
        "RFC 6991 Common YANG Data Types";
    }
    leaf flow-label {
      type inet:ipv6-flow-label;
      description
        "The flow label value of the header. IPv6 only.";
      reference
        "RFC 6991 Common YANG Data Types";
    }
    leaf source-port {
      type inet:port-number;
      description
        "The source port number.";
      reference
        "RFC 6991 Common YANG Data Types";
    }
    leaf destination-port {
      type inet:port-number;
      description
        "The destination port number.";
      reference
        "RFC 6991 Common YANG Data Types";
    }
  }

  grouping l2-header {
    description
      "The Ethernet or TSN packet header information.";
    leaf source-mac-address {
      type yang:mac-address;
      description
        "The source MAC address value of the Ethernet header.";
    }
    leaf destination-mac-address {
      type yang:mac-address;
      description
        "The destination MAC address value of the Ethernet header.";
    }
    leaf ethertype {
      type ethertypes:ethertype;
      description
        "The Ethernet packet type value of the Ethernet header.";
    }
    leaf vlan-id {
      type dot1q-types:vlanid;
      description
        "The VLAN value of the Ethernet header.";
      reference
        "IEEE 802.1Q-2022.";
    }
    leaf pcp {
      type dot1q-types:priority-type;
      description
        "The priority value of the Ethernet header.";
      reference
        "IEEE 802.1Q-2022.";
    }
  }

  grouping destination-ip-port-id {
    description
      "The TCP/UDP port destination identification
       information.";
    container destination-port {
      uses packet-fields:port-range-or-operator;
      description
         "This grouping captures the destination port fields.";
    }
  }

  grouping source-ip-port-id {
    description
      "The TCP/UDP port source identification
       information.";
    container source-port {
      uses packet-fields:port-range-or-operator;
      description
         "This grouping captures the source port fields.";
    }
  }

  grouping ip-flow-id {
    description
      "The IPv4/IPv6 packet header identification information.";
    leaf src-ip-prefix {
      type inet:ip-prefix;
      description
        "The source IP prefix.";
      reference
        "RFC 6991 Common YANG Data Types";
    }
    leaf dest-ip-prefix {
      type inet:ip-prefix;
      description
        "The destination IP prefix.";
      reference
        "RFC 6991 Common YANG Data Types";
    }
    leaf protocol-next-header {
      type uint8;
      description
        "Internet Protocol number.  Refers to the protocol of the
         payload.  In IPv6, this field is known as 'next-header', and
         if extension headers are present, the protocol is present in
         the 'upper-layer' header.";
      reference
        "RFC 791: Internet Protocol
         RFC 8200: Internet Protocol, Version 6 (IPv6)
         Specification.";
    }
    leaf dscp {
      type inet:dscp;
      description
        "The traffic class value in the header.";
      reference
        "RFC 6991 Common YANG Data Types";
    }
    leaf flow-label {
      type inet:ipv6-flow-label;
      description
        "The flow label value of the header.";
      reference
        "RFC 6991 Common YANG Data Types";
    }
    uses source-ip-port-id;
    uses destination-ip-port-id;
    leaf ipsec-spi {
      type ipsec-spi;
      description
      "IPsec Security Parameters Index of the Security
       Association.";
      reference
        "IETF RFC 4303 Encapsulating Security Payload (ESP).";
    }
  }

  grouping mpls-flow-id {
    description
      "The MPLS packet header identification information.";
    choice label-space {
      description
        "Designates the label space being used.";
      case context-label-space {
        uses rt-types:mpls-label-stack;
      }
      case platform-label-space {
        leaf label {
          type rt-types:mpls-label;
          description
           "This is the case for Platform label space.";
        }
      }
    }
  }

  grouping data-flow-spec {
    description
      "app-flow identification.";
    choice data-flow-type {
      description
        "The Application flow type choices.";
      container tsn-app-flow {
        uses l2-header;
        description
          "The L2 header for application.";
      }
      container ip-app-flow {
        uses ip-flow-id;
        description
          "The IP header for application.";
      }
      container mpls-app-flow {
        uses mpls-flow-id;
        description
          "The MPLS header for application.";
      }
    }
  }

  grouping detnet-flow-spec {
    description
      "detnet-flow identification.";
    choice detnet-flow-type {
      description
        "The DetNet flow type choices.";
      case ip-detnet-flow {
        uses ip-flow-id;
      }
      case mpls-detnet-flow {
        uses mpls-flow-id;
      }
    }
  }

  grouping app-flows-group {
    description
      "Incoming or outgoing app-flow reference group.";
    leaf-list flow {
      type app-flow-ref;
      description
        "List of ingress or egress app-flows.";
    }
  }

  grouping service-sub-layer-group {
    description
      "Incoming or outgoing service sub-layer reference group.";
    leaf-list sub-layer {
      type service-sub-layer-ref;
      description
        "List of incoming or outgoing service sub-layers that have
         to aggregate or disaggregate.";
    }
  }

  grouping forwarding-sub-layer-group {
    description
      "Incoming or outgoing forwarding sub-layer reference group.";
    leaf-list sub-layer {
      type forwarding-sub-layer-ref;
      description
        "List of incoming or outgoing forwarding sub-layers that
         have to aggregate or disaggregate.";
    }
  }

  grouping detnet-header {
    description
      "DetNet header info for DetNet encapsulation or swap.";
    choice header-type {
      description
      "The choice of DetNet header type.";
      case mpls {
        description
          "MPLS label stack for DetNet MPLS encapsulation or
           forwarding.";
        uses rt-types:mpls-label-stack;
      }
      case ip {
        description
          "IPv4/IPv6 packet header for DetNet IP encapsulation.";
        uses ip-header;
      }
    }
  }

  grouping detnet-app-next-hop-content {
    description
      "Generic parameters of DetNet next hops. This follows the 
       principles for next hops in RFC 8349";
    choice next-hop-options {
      description
        "Options for next hops.  It is expected that further cases
         will be added through
         augments from other modules, e.g., for recursive
         next hops.";
      case simple-next-hop {
        description
          "This case represents a simple next hop consisting of the
           next-hop address and/or outgoing interface.";
        leaf outgoing-interface {
          type if:interface-ref;
          description
            "The outgoing interface, when matching all flows to
             the interface.";
        }
        choice flow-type {
          description 
            "The flow type choices.";
          case ip {
            leaf next-hop-address {
              type inet:ip-address;
              description
               "The IP next hop case.";
            }
          }
          case mpls {
            uses rt-types:mpls-label-stack;
            description
              "The MPLS label stack next hop case.";
          }
        }
      }
      case next-hop-list {
        description
          "Container for multiple next hops.";
        list next-hop {
          key "hop-index";
          description
            "An entry in a next-hop list.";
          leaf hop-index {
            type uint8;
            description
              "A user-specified identifier utilized to uniquely
               reference the next-hop entry in the next-hop list.
               The value of this index has no semantic meaning other
               than for referencing the entry.";
          }
          leaf outgoing-interface {
            type if:interface-ref;
            description
              "The outgoing interface, when matching all flows to
               the interface.";
          }
          choice flow-type {
            description
              "The flow types supported."; 
            case ip {
              leaf next-hop-address {
                type inet:ip-address;
                description
                  "This is the IP flow type next hop.";
              }
            }
            case mpls {
              uses rt-types:mpls-label-stack;
            }
          }
        }
      }
    }
  }

  grouping detnet-forwarding-next-hop-content {
    description
      "Generic parameters of DetNet next hops. This follows the 
       principles for next hops in RFC 8349";
    choice next-hop-options {
      description
        "Options for next hops.
         It is expected that further cases will be added through
         augments from other modules, e.g., for recursive
         next hops.";
       case simple-next-hop {
        description
          "This case represents a simple next hop consisting of the
           next-hop address and/or outgoing interface.";
        leaf outgoing-interface {
          type if:interface-ref;
          description
            "The outgoing interface, when matching all flows to
             the interface.";
        }
        choice flow-type {
          description
            "These are the flow type next hop choices.";
          case ip {
            description
              "Use IP data plane for forwarding.";
            leaf next-hop-address {
              type inet:ip-address;
              description
                "This is an IP address as a next hop.";
            }
            uses ip-header;
          }
          case mpls {
            description
              "Use MPLS data plane for forwarding.";
            uses rt-types:mpls-label-stack;
          }
        }
      }
      case next-hop-list {
        description
          "Container for multiple next hops.";
        list next-hop {
          key "hop-index";
          description
            "An entry in a next-hop list.";
          leaf hop-index {
            type uint8;
            description
              "The value of the index for a hop.";
          }
          leaf outgoing-interface {
            type if:interface-ref;
            description
              "The outgoing interface, when matching all flows to
               the interface.";
          }
          choice flow-type {
            description
              "These are the flow type next hop choices.";
            case ip {
              description
                "Use IP data plane for forwarding.";
              leaf next-hop-address {
                type inet:ip-address;
                description
                  "This is an IP address as a next hop.";
              }
              uses ip-header;
            }
            case mpls {
              description
                "Use MPLS data plane for forwarding.";
              uses rt-types:mpls-label-stack;
            }
          }
        }
      }
    }
  }

  container detnet {
    description
      "The top level DetNet container. This contains
       applications, service sub-layers and forwarding sub-layers
       as well as the traffic profiles.";
    list traffic-profile {
      key "name";
      description
        "A traffic profile.";
      leaf name {
        type string;
        description
          "The name of the traffic profile which is used as a
           reference to this profile.";
      }
      container traffic-requirements {
        description
          "This defines the attributes of the App-flow
           regarding bandwidth, latency, latency variation, loss, and
           misordering tolerance.";
        reference
          "RFC 9016 Section 5.9";
        leaf min-bandwidth {
          type uint64;
          units 'octets per second';
          description
            "This is the minimum bandwidth that has to be
             guaranteed for the DetNet service.  MinBandwidth is
             specified in octets per second.";
          reference
            "RFC 9016 Section 5.9.1";
        }
        leaf max-latency {
          type uint32;
          units "nanoseconds";
          description
            "This is the maximum latency from Ingress to
             Egress(es) for a single packet of the DetNet flow.
             MaxLatency is specified as an integer number of
             nanoseconds. The MAX value is 4,294,967,295 
             nanoseconds.";
          reference
            "RFC 9016 Section 5.9.2";
        }
        leaf max-latency-variation {
          type uint32;
          units "nanoseconds";
          description
            "This is the difference between the
             minimum and the maximum end-to-end one-way latency.
             MaxLatencyVariation is specified as an integer number of
             nanoseconds.";
          reference
            "RFC 9016 Section 5.9.3";
        }
        leaf max-loss {
          type decimal64 {
            fraction-digits 10;
            range "0 .. 100";
          }
          units "percent";
          description
            "This defines the maximum Packet Loss Rate (PLR)
            parameter for the DetNet service between the Ingress and
            Egress(es) of the DetNet domain. Packet loss rate is
            calculated by the number of transmitted packets minus
            the number of received packets divided by the number
            transmitted packets expressed as a percent.";
          reference
            "RFC 9016 Section 5.9.4";
        }
        leaf max-consecutive-loss-tolerance {
          type uint32;
          units "packets";
          description
            "Some applications have special loss requirement, such
             as MaxConsecutiveLossTolerance.  The maximum consecutive
             loss tolerance parameter describes the maximum number of
             consecutive packets whose loss can be tolerated.  The
             maximum consecutive loss tolerance can be measured for
             example based on sequence number.";
          reference
            "RFC 9016 Section 5.9.5";
        }
        leaf max-misordering {
          type uint32;
          units "packets";
          description
            "This describes the tolerable maximum number
             of packets that can be received out of order.  The
             maximum allowed misordering can be measured for example
             based on sequence number.  The value zero for the
             maximum allowed misordering indicates that in order
             delivery is required, misordering cannot be tolerated.";
          reference
            "RFC 9016 Section 5.9.6";
        }
      }
      container traffic-spec {
        description
          "Traffic-specification specifies how the Source transmits
           packets for the flow.  This is the promise/request of the
           Source to the network.  The network uses this flow
           specification to allocate resources and adjust queue
           parameters in network nodes.";
        reference
          "RFC 9016 Section 5.5";
        leaf interval {
          type uint32;
          units "nanoseconds";
          description
            "The period of time in which the traffic
             specification should not be exceeded.";
          reference
            "RFC 9016 Section 5.5,
             IEEE802.1Q";
        }
        leaf max-pkts-per-interval {
          type uint32;
          description
            "The maximum number of packets that the
             source will transmit in one interval.";
          reference
            "RFC 9016 Section 5.5, IEEE802.1Q";
        }
        leaf max-payload-size {
          type uint32;
          description
            "The maximum payload size that the source
             will transmit.";
          reference
            "RFC 9016 Section 5.5, IEEE802.1Q";
        }
        leaf min-payload-size {
          type uint32;
          description
            "The minimum payload size that the source
             will transmit., IEEE802.1Q";
        }
        leaf min-pkts-per-interval {
          type uint32;
          description
            "The minimum number of packets that the
             source will transmit in one interval.";
          reference
            "RFC 9016 Section 5.5, IEEE802.1Q";
        }
      }
      leaf-list member-app-flow {
        type app-flow-ref;
        config false;
        description
          "A list of Applications attached to this profile.  Each
          application that uses a profile has an automatically
          populated reference.";
        reference
          "RFC XXXX: Deterministic Networking (DetNet) YANG Model
          Section 5";
      }
      leaf-list member-svc-sublayer {
        type service-sub-layer-ref;
        config false;
        description
          "A list of Service Sub-layers attached to this profile.
          Each Service Sub-layers that uses a profile has an
          automatically populated reference.";
        reference
          "RFC XXXX: Deterministic Networking (DetNet) YANG Model
          Section 5";
      }
      leaf-list member-fwd-sublayer {
        type forwarding-sub-layer-ref;
        config false;
        description
          "A list of Forwarding Sub-layers attached to this profile.
          Each Forwarding Sub-layers that uses a profile has an
          automatically populated reference.";
        reference
          "RFC XXXX: Deterministic Networking (DetNet) YANG Model
          Section 5";
      }
    }
    container app-flows {
      description
        "The DetNet app-flow configuration.";
      reference
        "RFC 9016 Section 4.1";
      list app-flow {
        key "name";
        description
          "A unique (management) identifier of the App-flow.";
        leaf name {
          type string;
          description
            "A unique (management) identifier of the App-flow.";
          reference
            "RFC 9016
             Sections 4.1, 5.1";
        }
        leaf bidir-congruent {
          type boolean;
          default false;
          description
            "Defines the data path requirement of the App-flow
             whether it must share the same data path and physical
             path for both directions through the network, e.g., to
             provide congruent paths in the two directions.";
          reference
            "RFC 9016 
             Section 4.2";
        }
        leaf outgoing-service {
          type service-sub-layer-ref;
          config false;
          description
            "Binding to this applications outgoing
             service.";
        }
        leaf incoming-service {
          type service-sub-layer-ref;
          config false;
          description
            "Binding to this applications incoming service.";
        }
        leaf traffic-profile {
          type traffic-profile-ref;
          description
            "The Traffic Profile for this group.";
        }
        container ingress {
          description
            "Ingress DetNet application flows or a compound flow.";
          leaf app-flow-status {
            type identityref {
              base app-status;
            }
            default none;
            config false;
            description
              "Status of ingress application flow. This is an
               operational status and defaults to none if 
               incomplete.";
            reference
              "RFC 9016 Sections
               4.1, 5.8";
          }
          leaf-list interface {
            type if:interface-ref;
            description
            "Interface is optional for a service type. When
             matching a flow to a single interface one
             interface is specified. The list allows for
             matching a subset of interfaces. When more
             than one interfaces is specified, these
             flows are simply aggregated and the service
             sub-layer is unaware of the aggregation.";
          }
          uses data-flow-spec;
        } //End of app-ingress
        container egress {
          description
            "Egress DetNet application flows or a compound flow.";
          uses data-flow-spec;
          choice application-type {
            description
              "This is the application type choices.";
            container ethernet {
              description
                "This is Ethernet or TSN traffic that maps to an
                interface.";
              leaf-list interface {
                type if:interface-ref;
                description
                  "This is one or more Ethernet or TSN interfaces.
                   If multiple interfaces are specified, this 
                   application flow is replicated to those 
                   interfaces.  DetNet application Flow filtering
                   applies to the whole list of interfaces.
                   For fine grain flow filtering, use a single
                   interface per application.";
              }
            }
            container ip-mpls {
              description
                "This is IP or MPLS DetNet application types.";
              uses detnet-app-next-hop-content;
            }
          }
        }
      }
    }
    container service {
      description
        "The DetNet service sub-layer configuration.";
      list sub-layer {
        key "name";
        description
          "Services are indexed by name.";
        leaf name {
          type string;
          description
            "The name of the DetNet service sub-layer.";
        }
        leaf service-rank {
          type uint8;
          default 255;
          description
            "The DetNet rank for this service. Defaults to 255 
            lowest rank if not specified.";
          reference
            "RFC 9016 Section 5.7.";
        }
        leaf traffic-profile {
          type traffic-profile-ref;
          description
            "The Traffic Profile for this service.";
        }
        container service-protection {
          description
            "This is the service protection type and sequence number 
             options.";
          leaf protection {
            type service-protection;
            description
              "The DetNet service protection type such as 
              Packet Replication Function (PRF), 
              Packet Elimination Function (PEF),
              Packet Replication, Elimination, and Ordering Functions
              (PREOF).";
            reference
              "RFC 8938 Section 4.3";
          }
          leaf sequence-number-length {
            type sequence-number-field;
            default zero-sn;
            description
              "Sequence number field length can be one of 0 (none),
               16-bits or 28-bits. The default is none.";
          }
        }
        leaf operation {
          type operation;
          description
            "This is the service operation type for this service 
             sub-layer;"; 
        }
        container incoming {
          description
            "The DetNet service sub-layer incoming configuration.";
          choice incoming {
            description
              "A service sub-layer may have App flows or other
               service sub-layers.";
            container app-flow {
              description
                "This service sub-layer is related to the app-flows
                 of the upper layer and provide ingress proxy or
                 ingress aggregation at the ingress node.";
              uses app-flows-group;
            }
            container service-aggregation {
              description
                "This service sub-layer is related to the service
                 sub-layer of the upper layer and provide
                 service-to-service aggregation at the ingress node
                 or relay node.";
              uses service-sub-layer-group;
            }
            container forwarding-aggregation {
              description
                "This service sub-layer is related to the forwarding
                 sub-layer of the upper layer and provide
                 forwarding-to-service aggregation at the ingress
                 node or relay node.";
              uses forwarding-sub-layer-group;
            }
            container service-id {
              description
                "This service sub-layer is related to the service or
                 forwarding sub-layer of the lower layer and provide
                 DetNet service relay or termination at the relay
                 node or egress node.";
              uses detnet-flow-spec;
            }
            container forwarding-sub-layer {
              description
                "This entry specifies one or more forwarding
                 sub-layers. No or minimal service sub-layer 
                 encapsulation is allowed.";
              leaf-list sub-layer {
                type forwarding-sub-layer-ref;
                config false;
                description
                  "List of outgoing forwarding sub-layers.";
               }
            }
          }
        }
        container outgoing {
          description
            "The DetNet service sub-layer outgoing configuration.";
          choice outgoing {
            description
              "The outgoing type may be a forwarding Sub-layer or a
               service sub-layer or aggregation type.";
            container forwarding-sub-layer {
              description
                "This service sub-layer is sending to the forwarding
                 sub-layers of the lower layer for DetNet service
                 forwarding or service-to-forwarding aggregation at
                 the ingress node or relay node.  When the operation
                 type is service-initiation, The service sub-layer
                 encapsulates the DetNet Control-Word and services
                 label, which are for individual DetNet flow when the
                 incoming type is app-flow and for aggregated DetNet
                 flow when the incoming type is service or
                 forwarding.  The service sub-layer swaps the service
                 label when the operation type is service-relay.";
              reference
                "RFC 8964 Section 4.2.1 and 4.2.2."; 
              list service-outgoing {
                key "index";
                description
                  "List of the outgoing service
                   that separately for each node
                   where services will be eliminated.";
                leaf index {
                  type uint8;
                  description
                    "This index allows a list of multiple outgoing 
                     forwarding sub-layers";
                }
                uses detnet-header;
                uses forwarding-sub-layer-group; 
              }
            }
            container service-sub-layer {
              description
                "This service sub-layer is sending to the service
                 sub-layers of the lower layer for service-to-service
                 aggregation at the ingress node or relay node.  The
                 service sub-layer encapsulates the DetNet
                 Control-Word and S-label when the operation type is
                 service-initiation, and swaps the S-label when the
                 operation type is service-relay.";
              reference
                "RFC 8964 Section 4.2.1 and 4.2.2."; 
              leaf aggregation-sub-layer {
                type service-sub-layer-ref;
                description
                  "reference point of the service-sub-layer
                   at which this service will be aggregated.";
              }
              container service-label {
                description
                  "This is the MPLS service sub-layer label. This
                  is optional and only used when the service
                  sub-layer uses MPLS. It is an MPLS stack since 
                  more than a single label may be used.";
                uses rt-types:mpls-label-stack;
              }
            }
            container app-flow {
              description
                "This service sub-layer is sending to the app-flow of
                 the upper layer for egress proxy at the egress node,
                 and decapsulates the DetNet Control-Word and S-label
                 for individual DetNet service.  This outgoing type
                 only can be chosen when the operation type is
                 service-termination.";
              reference
                "RFC 8964 Section 4.2.1 and 4.2.2."; 
              uses app-flows-group;
            }
            container service-disaggregation {
              description
                "This service sub-layer is sending to the service
                 sub-layer of the upper layer for service-to-service
                 disaggregation at the relay node or egress node, and
                 decapsulates the DetNet Control-Word and A-label for
                 aggregated DetNet service.  This outgoing type only
                 can be chosen when the operation type is
                 service-termination.";
              reference
                "RFC 8964 Section 4.2.1 and 4.2.2."; 
              uses service-sub-layer-group;
            }
            container forwarding-disaggregation {
              description
                "This service sub-layer is sending to the forwarding
                 sub-layer of the upper layer for
                 forwarding-to-service disaggregation at the relay
                 node or egress node, and decapsulates the DetNet
                 Control-Word and A-label for aggregated DetNet
                 service.  This outgoing type only can be chosen when
                 the operation type is service-termination.";
              reference
                "RFC 8964 Section 4.2.1 and 4.2.2."; 
              uses forwarding-sub-layer-group;
            }
          }
        }
      }
    }
    container forwarding {
      description
        "The DetNet forwarding sub-layer configuration.";
      list sub-layer {
        key "name";
        description
          "The list is one or more DetNet service/forwarding types.";
        leaf name {
          type string;
          description
            "The name of the DetNet forwarding sub-layer.";
        }
        leaf traffic-profile {
          type traffic-profile-ref;
          description
            "The Traffic Profile for this group.";
        }
        leaf operation {
          type mpls-fwd-operation;
          description
            "This is the forwarding operation types 
             impose-and-forward, pop-and-forward, 
             pop-impose-and-forward, forward, pop-and-lookup.";
        }
        container incoming {
          description
            "The DetNet forwarding sub-layer incoming 
             configuration.";
          choice incoming {
            description
              "Cases of incoming types.";
            container service-sub-layer {
              description
                "This forwarding sub-layer is related to the service
                 sub-layers of the upper layer and provide DetNet
                 forwarding or service-to-forwarding aggregation at
                 the ingress node or relay node.";
              uses service-sub-layer-group;
            }
            container forwarding-aggregation {
              description
                "This forwarding sub-layer is related to the
                 forwarding sub-layer of the upper layer and provide
                 forwarding-to-forwarding aggregation at the ingress
                 node or relay node or transit node.";
              uses forwarding-sub-layer-group;
            }
            container forwarding-id  {
              description
                "This forwarding sub-layer is related to all of the
                 lower layer and provide DetNet forwarding swap or
                 termination at the transit node or relay node or
                 egress node.";
              leaf interface {
                type if:interface-ref;
                description
                  "This is the interface associated with the
                   forwarding sub-layer.";
              }
              uses detnet-flow-spec;
            }
          }
        }
        container outgoing {
          description
            "The DetNet forwarding sub-layer outbound
             configuration.";
          choice outgoing {
            description
              "This is when a service connected directly to an
              interface with no forwarding sub-layer."; 
            container
              interface {
              description
                "This forwarding sub-layer is sending to the
                 interface for send to next-hop at the ingress
                 node or relay node or transit node.";
              uses detnet-forwarding-next-hop-content;
            }
            container service-aggregation {
              description
                "This forwarding sub-layer is sending to the service
                 sub-layers of the lower layer for
                 forwarding-to-service aggregation at the ingress
                 node or relay node.";
              leaf aggregation-sub-layer {
                type service-sub-layer-ref;
                description
                  "This is a reference to the service sub-layer.";
              }
              container optional-forwarding-label {
                description 
                  "This is the optional forwarding label for service 
                   aggregation.";
                uses rt-types:mpls-label-stack;
              }
            }
            container forwarding-sub-layer {
              description
                "This forwarding sub-layer is sending to the
                 forwarding sub-layers of the lower layer for
                 forwarding-to-forwarding aggregation at the ingress
                 node or relay node or transit node.";
              leaf aggregation-sub-layer {
                type forwarding-sub-layer-ref;
                description
                  "This is a reference to the forwarding sub-layer.";
              }
              container forwarding-label {
                description
                  "This is the forwarding label for forwarding
                   sub-layer aggregation.";
                uses rt-types:mpls-label-stack;
              }
            }
            container service-sub-layer {
              description
                "This forwarding sub-layer is sending to the service
                 sub-layer of the upper layer and decapsulate the
                 F-label for DetNet service or service-to-forwarding
                 disaggregation at the relay node or egress node.
                 This outgoing type only can be chosen when the
                 operation type is pop-and-lookup.";
              uses service-sub-layer-group;
              reference
                "RFC 8964 Section 4.2.3";
            }
            container forwarding-disaggregation {
              description
                "This forwarding sub-layer is sending to the
                 forwarding sub-layer of the upper layer and
                 decapsulate the F-label for forwarding-to-forwarding
                 disaggregation at the transit node or relay node or
                 egress node.  This outgoing type only can be chosen
                 when the operation type is pop-and-lookup.";
              uses forwarding-sub-layer-group;
            }
          }
        }
      }
    }
  }
}
